(defun list_layers_write (outpath / acad doc lays f name ss cnt)
  (vl-load-com)
  (setq acad (vlax-get-acad-object))
  (setq doc (vla-get-ActiveDocument acad))
  (setq lays (vla-get-Layers doc))
  (setq f (open outpath "w"))
  (if (not f) (progn (princ (strcat "Failed to open " outpath)) (princ)) )
  (vlax-for lay lays
    (setq name (vla-get-Name lay))
    (setq ss (ssget "_X" (list (cons 8 name))))
    (setq cnt (if ss (sslength ss) 0))
    (write-line (strcat name ";" (itoa cnt)) f)
  )
  (close f)
  (princ)
)
